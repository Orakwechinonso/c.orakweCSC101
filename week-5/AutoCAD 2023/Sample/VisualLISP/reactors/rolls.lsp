;;;                                                                    ;
;;;  ROLLS.LSP                                                         ;
;;;                                                                    ;
;;;  Copyright 1987, 1988, 1990, 1992, 1994, 1996, 1997, 1998, 1999    ;
;;;  by Autodesk, Inc. All Rights Reserved.                            ;
;;;                                                                    ;
;;;  You are hereby granted permission to use, copy and modify this    ;
;;;  software without charge, provided you do so exclusively for       ;
;;;  your own use or for use by others in your organization in the     ;
;;;  performance of their normal duties, and provided further that     ;
;;;  the above copyright notice appears in all copies and both that    ;
;;;  copyright notice and the limited warranty and restricted rights   ;
;;;  notice below appear in all supporting documentation.              ;
;;;                                                                    ;
;;;  Incorporation of any part of this software into other software,   ;
;;;  except when such incorporation is exclusively for your own use    ;
;;;  or for use by others in your organization in the performance of   ;
;;;  their normal duties, is prohibited without the prior written      ;
;;;  consent of Autodesk, Inc.                                         ;
;;;                                                                    ;
;;;  Copying, modification and distribution of this software or any    ;
;;;  part thereof in any form except as expressly provided herein is   ;
;;;  prohibited without the prior written consent of Autodesk, Inc.    ;
;;;                                                                    ;
;;;  AUTODESK PROVIDES THIS SOFTWARE "AS IS" AND WITH ALL FAULTS.      ;
;;;  AUTODESK SPECIFICALLY DISCLAIMS ANY IMPLIED WARRANTY OF           ;
;;;  MERCHANTABILITY OR FITNESS FOR A PARTICULAR USE.  AUTODESK,       ;
;;;  INC. DOES NOT WARRANT THAT THE OPERATION OF THE SOFTWARE          ;
;;;  WILL BE UNINTERRUPTED OR ERROR FREE.                              ;
;;;                                                                    ;
;;;  Restricted Rights for US Government Users.  This software         ;
;;;  and Documentation are provided with RESTRICTED RIGHTS for US      ;
;;;  US Government users.  Use, duplication, or disclosure by the      ;
;;;  Government is subject to restrictions as set forth in FAR         ;
;;;  12.212 (Commercial Computer Software-Restricted Rights) and       ;
;;;  DFAR 227.7202 (Rights in Technical Data and Computer Software),   ;
;;;  as applicable.  Manufacturer is Autodesk, Inc., 111 McInnis       ;
;;;  Parkway, San Rafael, California 94903.                            ;
;;;                                                                    ;

;;;--------------------------------------------------------------------;
;;; General Note:  THIS FILE IS A MEMBER OF THE REAC-TST PROJECT       ;
;;;--------------------------------------------------------------------;
;;; This file contains an example of object and editor reactors.       ;
;;;--------------------------------------------------------------------;

;;;--------------------------------------------------------------------;
;;;       Function:  NUM-OF-CIRCLES                                    ;
;;;                                                                    ;
;;;    Description:  This function calculates how many circles         ;
;;;                  can be contained within a circle.                 ;
;;;                                                                    ;
;;;      Arguments:                                                    ;
;;;      big-radius = a number denoting a radius.                      ;
;;;    small-radius = a number denoting a radius.                      ;
;;;                                                                    ;
;;; Returned Value:  A number representing the number of circles.      ;
;;;                                                                    ;
;;;          Usage:                                                    ;
;;;               (num-of-circles 12 5)                                ;
;;;--------------------------------------------------------------------;
(defun num-of-circles (big-radius small-radius)
  ;;  (fix (/ (* pi big-radius) small-radius))  ;; Voided
  (fix
    (/ pi
       (atan
	 (/ small-radius
	    (sqrt
	      (- (* big-radius big-radius) (* small-radius small-radius))
	    )
	 )
       )
    )
  )
)

;;;--------------------------------------------------------------------;
;;;       Function:  REACTOR-M-CIRCLE-RADIUS                           ;
;;;                                                                    ;
;;;    Description:  This function will be called inside a             ;
;;;                  :vlr-modified event. It is responsible for        ;
;;;                  recalculating the quantity of circles.            ;
;;;                                                                    ;
;;;                  Required Functions:                               ;
;;;                    num-of-circles                                  ;
;;;                    make-circles-on-circle                          ;
;;;                    get-model-space                                 ;
;;;                                                                    ;
;;;      Arguments:                                                    ;
;;;        notifier = a valid vla object. Filled in by the calling     ;
;;;                   reactor.                                         ;
;;;         reactor = a valid vlr object reactor. Filled in by the     ;
;;;                   calling reactor.                                 ;
;;;        arg-list = argument list filled in by the calling reactor.  ;
;;;                   Filled in by the calling reactor.                ;
;;;                                                                    ;
;;; Returned Value:  A valid vla circle object.                        ;
;;;                                                                    ;
;;;          Usage:  Intended to be called from a reactor call back.   ;
;;;     (reactor-m-circle-radius notifier reactor arg-list)            ;
;;;--------------------------------------------------------------------;
(defun reactor-m-circle-radius (notifier     reactor	  arg-list
				/	     midle-circle circle1
				circle2	     m-new-rad	  c-new-rad
				circle-list  len	  num-circles
			       )
  (if (and
	(setq midle-circle (vlr-data reactor))
	(vlax-write-enabled-p midle-circle)
	(setq circle1 (vlax-ldata-get midle-circle "circle1"))
	(setq circle2 (vlax-ldata-get midle-circle "circle2"))
	(vlax-read-enabled-p circle1)
	(vlax-read-enabled-p circle2)
      )
    (progn
      (setq rad1	(vla-get-radius circle1)
	    rad2	(vla-get-radius circle2)
	    m-new-rad	(/ (+ rad1 rad2) 2) ;midle circle radius
	    circle-list	(vlax-ldata-get midle-circle "circles")
	    c-new-rad	(/ (abs (- rad1 rad2)) 2) ;roll  radius
	    len		(length circle-list) ;current number of rolls
	    num-circles	(num-of-circles m-new-rad c-new-rad)
					;new number of rolls
      )

      (if (not (= (vla-get-radius midle-circle) m-new-rad))
	(vla-put-radius midle-circle m-new-rad)
      )
      (if (not (= len num-circles))	;change number of rolls
	(progn
	  (foreach cl circle-list
	    (if	(not (vlax-erased-p cl))
	      (vla-Erase cl)
	    )
	  )
	  (setq	acadModel   (get-model-space)
		circle-list
			    (make-circles-on-circle
			      midle-circle
			      c-new-rad
			      num-circles
			    )
	  )
	  (vlax-ldata-put midle-circle "circles" circle-list)
	)
      )
      (if (and circle-list
	       (not (= (vla-get-radius (car circle-list)) c-new-rad))
	  )
	(foreach circle	circle-list
	  (if (vlax-write-enabled-p circle)
	    (vla-put-radius circle c-new-rad)
	  )
	)
      )
    )
  )
)

;;;--------------------------------------------------------------------;
;;;       Function:  CREATE-ROLLS                                      ;
;;;                                                                    ;
;;;    Description:  This function is responsible for passing          ;
;;;                  information to other procedures that display      ;
;;;                  the circles on the screen. Furthermore, this      ;
;;;                  function creates the neccesary reactor.           ;
;;;                                                                    ;
;;;                  Required Functions:                               ;
;;;                        num-of-circles                              ;
;;;                        circles-tied-to-curve                       ;
;;;                        create-same-reactor                         ;
;;;                        reactor-make-same-center                    ;
;;;                        reactor-m-circle-radius                     ;
;;;                                                                    ;
;;;      Arguments:                                                    ;
;;;         circle1 = a valid vla circle object.                       ;
;;;         circle2 = a valid vla circle object.                       ;
;;;                                                                    ;
;;; Returned Value:  A valid vlr object reactor                        ;
;;;                                                                    ;
;;;          Usage:                                                    ;
;;;               (create-rolls vla-circle1 vla-circle2)               ;
;;;--------------------------------------------------------------------;
(defun create-rolls (circle1	   circle2	 /
		     m-circle	   circles-list	 circle-reactor
		     rad	   num-circles	 acadModel
		    )
  (setq	acadModel      (get-model-space)
	m-circle       (make-middle-circle circle1 circle2)
	rad	       (/ (abs (- (vla-get-radius circle1) (vla-get-radius circle2)))
			  2
		       )
	num-circles    (num-of-circles (vla-get-radius m-circle) rad)
	circle-reactor (circles-tied-to-curve m-circle rad num-circles)
	circles-list   (vlax-ldata-get m-circle "circles")
  )
  (list
    (create-same-reactor
      (list circle1 circle2 m-circle)
      (function reactor-make-same-center)
    )
    (VLR-Object-reactor
      (list circle1 circle2)
      m-circle
      (list
	(cons :vlr-modified (function reactor-m-circle-radius))
      )
    )
    circle-reactor
  )
)

;;;--------------------------------------------------------------------;
;;;       Function:  MAKE-MIDDLE-CIRCLE                                ;
;;;                                                                    ;
;;;    Description:  This function is responsible for creating         ;
;;;                  a small circle between the two vla                ;
;;;                  circle objects.                                   ;
;;;                                                                    ;
;;;                  Required Functions:                               ;
;;;                        load-line-types                             ;
;;;                        get-model-space                             ;
;;;                                                                    ;
;;;      Arguments:                                                    ;
;;;         circle1 = a valid vla circle object.                       ;
;;;         circle2 = a valid vla circle object.                       ;
;;;                                                                    ;
;;; Returned Value:  A valid vla circle object.                        ;
;;;                                                                    ;
;;;          Usage:                                                    ;
;;;               (make-middle-circle vla-circle1 vla-circle2)         ;
;;;--------------------------------------------------------------------;
(defun make-middle-circle (circle1 circle2 / middle-circle)
  (setq	middle-circle
	 (vla-AddCircle
	   (get-model-space)
	   (vla-get-center circle1)
	   (/ (+ (vla-get-radius circle1) (vla-get-radius circle2)) 2)
	 )
  )
  (if (load-line-types "Dashdot" "acad.lin")
    (vla-put-Linetype middle-circle "Dashdot"))
  (vlax-ldata-put middle-circle "circle1" circle1)
  (vlax-ldata-put middle-circle "circle2" circle2)
  (vla-put-Color circle1 acRed)
  (vla-put-Color circle2 acRed)
  middle-circle
)

;;;--------------------------------------------------------------------;
;;;       Function:  C:ROLLS-TST                                       ;
;;;                                                                    ;
;;;    Description:  This function will create 4 circles. One outer    ;
;;;                  circle and three inner circles.                   ;
;;;                                                                    ;
;;;                  Required Functions:                               ;
;;;                    get-model-space                                 ;
;;;                    create-rolls                                    ;
;;;                                                                    ;
;;;      Arguments:  none                                              ;
;;;                                                                    ;
;;; Returned Value:  A valid reactor object.                           ;
;;;                                                                    ;
;;;          Usage: (C:ROLLS-TST) or ROLLS-TST from                    ;
;;;                 the ACAD Command: prompt.                          ;
;;;--------------------------------------------------------------------;
(defun C:ROLLS-TST (/ center circle1 circle2 radius1 radius2 acadModel)
  (initget 1)				
  (setq center (GETPOINT "\nSelect center"))
  (initget 103)				;(+ 1 2 4 32 64)
  (setq rad1 (GETDIST center "\nSelect first raduis"))
  (initget 103)				;(+ 1 2 4 32 64)
  (setq rad2 (GETDIST center "\nSelect second raduis"))
  (terpri)
  (setq	acadModel (get-model-space)
	circle1	  (vla-AddCircle acadModel (vlax-3d-point center) rad1)
	circle2	  (vla-AddCircle acadModel (vlax-3d-point center) rad2)
  )
  (create-rolls circle1 circle2)
)


;;;--------------------------------------------------------------------;
;;;       Function:  C:ROLLS-INFO                                      ;
;;;                                                                    ;
;;;    Description:  This function displays a help file in the ACAD    ;
;;;                  Command: prompt.                                  ;
;;;                                                                    ;
;;;      Arguments:  none                                              ;
;;;                                                                    ;
;;; Returned Value:  none                                              ;
;;;                                                                    ;
;;;          Usage: (C:ROLLS-INFO) or ROLLS-INFO from                  ;
;;;                 the ACAD Command: prompt.                          ;
;;;--------------------------------------------------------------------;
(defun C:ROLLS-INFO ()
  (princ "\nTo run test call ROLLS-TST")
  (princ "\nYou will be asked to select a center,")
  (princ "\na radius of the first circle and the radius of the second circle.")
  (princ "\nTwo circles (colored red) will be drawn.")
  (princ "\nThe space between them will be filled with rolls (circles)")
  (princ "\nEach time you change position of one of the red circles the")
  (princ "\nscheme will also change.")
  (princ "\nEach time you change radius of one of the red circles ")
  (princ "\nthe optimal number of rolls will be recalculated and if needed")
  (princ "\nchanged.")
  (princ "\n")
  (princ)
)


;;;--------------------------------------------------------------------;
;;; Add the functions within this file to the global functions list    ;
;;; to be used by the C:REACT-TEST-INFO function in R-INFO.LSP         ;
;;;--------------------------------------------------------------------;
(setq *REACT-TEST-COMMANDS-INFO*
       (cons (list "ROLLS-TST" "ROLLS-INFO")
	     *REACT-TEST-COMMANDS-INFO*))
	     
;; EOF

;;;-----BEGIN-SIGNATURE-----
;;; UAoAADCCCkwGCSqGSIb3DQEHAqCCCj0wggo5AgEBMQ8wDQYJKoZIhvcNAQELBQAw
;;; CwYJKoZIhvcNAQcBoIIHaDCCB2QwggVMoAMCAQICEA2+4xGUyzuWyBkNEt7WBCEw
;;; DQYJKoZIhvcNAQELBQAwaTELMAkGA1UEBhMCVVMxFzAVBgNVBAoTDkRpZ2lDZXJ0
;;; LCBJbmMuMUEwPwYDVQQDEzhEaWdpQ2VydCBUcnVzdGVkIEc0IENvZGUgU2lnbmlu
;;; ZyBSU0E0MDk2IFNIQTM4NCAyMDIxIENBMTAeFw0yMTA4MDIwMDAwMDBaFw0yMjA4
;;; MDIyMzU5NTlaMGkxCzAJBgNVBAYTAlVTMRMwEQYDVQQIEwpDYWxpZm9ybmlhMRMw
;;; EQYDVQQHEwpTYW4gUmFmYWVsMRcwFQYDVQQKEw5BdXRvZGVzaywgSW5jLjEXMBUG
;;; A1UEAxMOQXV0b2Rlc2ssIEluYy4wggIiMA0GCSqGSIb3DQEBAQUAA4ICDwAwggIK
;;; AoICAQDY65QEUknk2Yy87p4LaXMXOT7AasB4BhNRJKfabtvF7wt0+TnhDOnKHKB1
;;; NvRywfn6n9qqIXN2pGjRuzWhJmjzb0C3+jA+c2Zlcp3VvisPdlizGFNzrL37XYoE
;;; yv7vg9fTKpDqiQS513cmJ8Kj38XWO55bEhAsiH6xgE9HiiD/XEUW8FUGAamdUIDD
;;; cq+NhdYsI5wgFyQM/CioZ8wttF0qJqSE4hbTaw8j2UFkDEkiFex4mCB99g7Dbzw+
;;; erXCEQCJuFYCQQN8OB8pxvTT/m8yYLYPwg9DzqVjn5SlhjLGdiPyOocuteb4QiM/
;;; JHZpRk8MQUs+wopTGDpYDhR8jfnbldfwvtwHfSPtKvq5QzErTVv9okB34Z0SaM86
;;; 518EZwUkrNfymt45CNmfa80uqC2xS+N7g4sg87EDbRCxvAnhJ6btFYRHhKfW6oAT
;;; YZFSU/4W3NFmX27Pnx8ZjATVPzoZ47rNm0JT2W4omIgfdq07Iu3SQp/e5a1QJpBY
;;; yaoT1ueqtxTdhBRHwjC5rTjVxuIQ24r9KU4ysH8R7d8skbBWGhyw2/9MB8rc6S7b
;;; g224JNJjgn0bM3cXOZRyBj8MkwWRU0XUV2wf6L1DDD9E8kBaagDv5J04VfScvtYK
;;; I+blbu8sT8is2fCnHptcPv0G4DFWOmkwFgOM6+OQoS5KsORz3wIDAQABo4ICBjCC
;;; AgIwHwYDVR0jBBgwFoAUaDfg67Y7+F8Rhvv+YXsIiGX0TkIwHQYDVR0OBBYEFDo+
;;; 4eCS86cJ84X74B6P0/A+TOO9MA4GA1UdDwEB/wQEAwIHgDATBgNVHSUEDDAKBggr
;;; BgEFBQcDAzCBtQYDVR0fBIGtMIGqMFOgUaBPhk1odHRwOi8vY3JsMy5kaWdpY2Vy
;;; dC5jb20vRGlnaUNlcnRUcnVzdGVkRzRDb2RlU2lnbmluZ1JTQTQwOTZTSEEzODQy
;;; MDIxQ0ExLmNybDBToFGgT4ZNaHR0cDovL2NybDQuZGlnaWNlcnQuY29tL0RpZ2lD
;;; ZXJ0VHJ1c3RlZEc0Q29kZVNpZ25pbmdSU0E0MDk2U0hBMzg0MjAyMUNBMS5jcmww
;;; PgYDVR0gBDcwNTAzBgZngQwBBAEwKTAnBggrBgEFBQcCARYbaHR0cDovL3d3dy5k
;;; aWdpY2VydC5jb20vQ1BTMIGUBggrBgEFBQcBAQSBhzCBhDAkBggrBgEFBQcwAYYY
;;; aHR0cDovL29jc3AuZGlnaWNlcnQuY29tMFwGCCsGAQUFBzAChlBodHRwOi8vY2Fj
;;; ZXJ0cy5kaWdpY2VydC5jb20vRGlnaUNlcnRUcnVzdGVkRzRDb2RlU2lnbmluZ1JT
;;; QTQwOTZTSEEzODQyMDIxQ0ExLmNydDAMBgNVHRMBAf8EAjAAMA0GCSqGSIb3DQEB
;;; CwUAA4ICAQBgAlhYjdQROM/ERZDYg0G6w3OPW7R5964dUS85Ijbkghpqi1KZB88n
;;; 0ItnNMz8nm0juZI7Jk1Jz+3fs4bcpfJrt4NQFaD9K1SAszXwe1zfBs0KTMqNkr7u
;;; Ji2ySyK6eFkO+ZRbKLIufwXPmY8uopzwjqn2BSoX/Q4ZOhw1H7tBxcudzOivMoL1
;;; ouUFPwAq3rN9mUl4G6nXrDvd31z24Q+dWtAA16cJbu2OgX2Tv7m7NPZIQ002iQCa
;;; ke59VqhiiUveM5UJ7Rr+Kdp732ZnGuKcGcbNl3B4KUjE1z6+wWaVJlygJX4EHZDn
;;; W+vtPcGRR3IHDWconSphlRZC7P1HhnAnfJqu7v5zyDv9+KyNL0hNNdWf0epK22HS
;;; BDC68W1DhC0ocWCFRHttRDqvvRyUhaAQBhIu7MoUzpi6hgg1S3sqM3u1D4f/Zn2C
;;; ocvEH9FOV0bq3ZOnCZjpH2HURTINElaDgM+hSfGN2zpbJSf1UKZXjkujYul75tk8
;;; 6ogI3b44wb4QdZskaIKxhw4/VZPbt31BHY2HbYCjFmvtpObX9qRwhG57EwK+o5mh
;;; KwkWifU7a8/5P1zyIwJfKdutGdB20wX9HRYPF+Bb87nKGJV/bM1tqzyRAIMGBWp/
;;; LLIee8R+FRMe7RT+v8/hRYsjPU2EVqSqweN2Fbz/rDeKSCr6Nl7XPjGCAqgwggKk
;;; AgEBMH0waTELMAkGA1UEBhMCVVMxFzAVBgNVBAoTDkRpZ2lDZXJ0LCBJbmMuMUEw
;;; PwYDVQQDEzhEaWdpQ2VydCBUcnVzdGVkIEc0IENvZGUgU2lnbmluZyBSU0E0MDk2
;;; IFNIQTM4NCAyMDIxIENBMQIQDb7jEZTLO5bIGQ0S3tYEITANBgkqhkiG9w0BAQsF
;;; ADANBgkqhkiG9w0BAQEFAASCAgB9Bl09rwZwipeVksg9B59FK+Gpb9M0WPE0qERP
;;; GVgpPzYhzrVjaZFsgM4TKsy8pJvpFQz/BOvA+pwHS4ynE4aeH4IjxM+1ZZFMtwNv
;;; TYdVciahytjbIRaEVlNUZLGRKZ2QK0OacIZMaIKRW2dtiAq0WY+k4DLqlI8uQfjH
;;; bN0H8zFaM7W9bZYJB2QcwF5aGg8ugB2LA4OZ0gJNp32FC1G4ggBhkDGahclDCej4
;;; GraaYtzKpvVgsBGDshIir3eZTbx3n3xjnhsD7QSb+zw5VNsiNr5gkE9NT9VRE/Bv
;;; R3nF0Zsy5PDqYtf6U0BQU09H1iYM46GBuCNIsSXYKF/N4S2dpQdIctAc7yJmuJc+
;;; 0+tQedXNiLjSAIwNwCvlkZCVYzvQfHu/2Ra60mc9Vlp2pbVdM5v2T1OkjUSFnXAa
;;; ylNUrAB1aFP7JTYHVPlbgzUOqW/2HVEtUbmNMID4SoW1Y52jgWzDJKhnUQjVPZl8
;;; CcXEQAaLu8BzHY5VchkYWVkGNaXb0XpZ+lOBWINAkNgBLigdOr8JDEnhhQcJUMb/
;;; B9IO50ygWnFK0UDrZsOJtU4hr+2tn9F8fD+4LHskK4po0E5ATiIqwaRIbPeRv15p
;;; P1G8qptdLBGMp/doOMPtEzuOPQ3AVJ8oegx8/mQMwIQjTlQkwOpqo9rNVtfdVpo2
;;; AHZzMg==
;;; -----END-SIGNATURE-----
